// Generated by EYangPreprocessorUtil (1.12.0-SNAPSHOT 2019-10-09 17:32:48 CEST) on Oct 11, 2019 7:24:25 AM
submodule nrf-submodule-discovery {
    yang-version "1.1";

    // module identification
    belongs-to ericsson-nrf {
        prefix "nrfe";
    }

    // linkage statements
    import tailf-common {
        prefix tailf;
    }
    import ericsson-yang-extensions {
        prefix yexte;
    }

    import ericsson-nrf-common {
        prefix nrfce;
    }

    organization
      "Ericsson AB";
    contact
      "Ericsson first line support via email";
    description
      "nrf submodule discovery.
       Copyright (c) 2018 Ericsson AB. All rights reserved.";

    revision "2019-09-04" {
        description
          "1, refine cm modeling;
           2, update ericsson-5gcudmpol-common to v1.0.1";
        yexte:version 1;
        yexte:release 0;
        yexte:correction 7;
    }

    revision "2019-04-03" {
        description
          "align design rule";
        yexte:version 1;
        yexte:release 0;
        yexte:correction 6;
    }

    revision "2019-01-16" {
        description
          "Change uint54 to uint32";
        yexte:version 1;
        yexte:release 0;
        yexte:correction 6;
    }

    revision "2018-12-12" {
        description
          "Add local-cache-timeout,local-cache-capacity,local-cache-enable";
        yexte:version 1;
        yexte:release 0;
        yexte:correction 5;
    }

    revision "2018-11-08" {
        description
          "Add hierarchy-discovery-mode";
        yexte:version 1;
        yexte:release 0;
        yexte:correction 4;
    }

    revision "2018-10-15" {
        description
          "Add default value for discovery-cache-time";
        yexte:version 1;
        yexte:release 0;
        yexte:correction 3;
    }

    revision "2018-09-03" {
        description
          "Add discovery_nf_service";
        yexte:version 1;
        yexte:release 0;
        yexte:correction 2;
    }

    revision "2018-08-01" {
        description
          "Updated nrf prefix";
        yexte:version 1;
        yexte:release 0;
        yexte:correction 1;
    }

    revision "2018-05-25" {
        description
          "Initial version. YANG modeling of 5G nrf";
        yexte:version 1;
        yexte:release 0;
        yexte:correction 0;
    }

    // module definitions
    grouping discovery-service {
        leaf response-cache-time {
            type uint32;
            default 86400;
            description
              "Time period for caching discovery result by NF Service Consumer.";
            tailf:callpoint cpa;
        }
        container local-cache {
            leaf enabled {
                type boolean;
                default false;
                description
                  "Indicate whether enable local cache when hierarchical NRFs are deployed. When enabled, NRF discovery caches NF Profiles from discovery result from other NRF.";
            }
            leaf timeout {
                type uint32;
                default 3000;
                description
                  "Time period for caching local cache in seconds.";
            }
            leaf capacity {
                type uint32;
                default 100;
                description
                  "Maximum number of local cache records.";
            }
            tailf:callpoint cpa;
        }
        container overload-redirection {
            description
              "NRF discovery overload redirection configuration.";
            uses nrfce:overload-redirection-profile;
            tailf:callpoint cpa;
        }
    }
}
