// Generated by EYangPreprocessorUtil (1.12.0-SNAPSHOT 2019-10-09 17:32:48 CEST) on Oct 11, 2019 7:24:25 AM
module ericsson-nrf {
    yang-version "1.1";
    namespace urn:rdns:com:ericsson:oammodel:ericsson-nrf;
    prefix nrfe;

    import tailf-common {
        prefix tailf;
    }
    import ericsson-yang-extensions {
        prefix yexte;
    }

    import ericsson-5gcudmpol-common {
        prefix udmp5gce;
    }

    import ericsson-nrf-common {
        prefix nrfce;
    }

    include "nrf-submodule-management";
    include "nrf-submodule-discovery";
    include "nrf-submodule-provisioning";
    include "nrf-submodule-policy";

    organization
      "Ericsson AB";
    contact
      "Ericsson first line support via email";
    description
      "5G NRF model.
       Copyright (c) 2018 Ericsson AB. All rights reserved.";

    revision "2019-09-04" {
        description
          "1, cm modeling refine;
           2, update ericsson-5gcudmpol-common to v1.0.1";
        yexte:version 1;
        yexte:release 0;
        yexte:correction 12;
    }
    revision "2019-04-24" {
        description
          "align with ericsson-5gcudmpol-common 0.1.4,
               align with design rule in UDM&P solution study
               update according to NRF CM review comments.";
        yexte:version 1;
        yexte:release 0;
        yexte:correction 11;
    }

    revision "2019-03-15" {
        description
          "Add witness-nf for geored-function";
        yexte:version 1;
        yexte:release 0;
        yexte:correction 10;
    }

    revision "2019-01-21" {
        description
          "Submodule nrf-submodule-management update to 1.0.5,
                 Submodule ericsson-nrf-common update to 0.1.3,
           Submodule submodule-sbi update to 1.0.5,
                 add submodule nrf-submodule-policy
                 add geored-function";
        yexte:version 1;
        yexte:release 0;
        yexte:correction 9;
    }

    revision "2018-12-12" {
        description
          "Submodule nrf-submodule-discovery update to 1.0.8";
        yexte:version 1;
        yexte:release 0;
        yexte:correction 8;
    }

    revision "2018-11-08" {
        description
          "Align 29.510 version 15.1.0";
        yexte:version 1;
        yexte:release 0;
        yexte:correction 7;
    }

    revision "2018-10-19" {
        description
          "Remove submodule-backend-db";
        yexte:version 1;
        yexte:release 0;
        yexte:correction 6;
    }

    revision "2018-10-15" {
        description
          "Remove default value of nrf-role";
        yexte:version 1;
        yexte:release 0;
        yexte:correction 5;
    }

    revision "2018-09-17" {
        description
          "Add nrf-submodule-provisioning";
        yexte:version 1;
        yexte:release 0;
        yexte:correction 4;
    }

    revision "2018-09-03" {
        description
          "Update name format, add nf-profile info, nf-common";
        yexte:version 1;
        yexte:release 0;
        yexte:correction 3;
    }

    revision "2018-08-03" {
        description
          "Update submodule-sbi";
        yexte:version 1;
        yexte:release 0;
        yexte:correction 2;
    }

    revision "2018-08-01" {
        description
          "Update submodule-sbi:fqdn and interPlmnFqdn to container";
        yexte:version 1;
        yexte:release 0;
        yexte:correction 1;
    }

    revision "2018-05-25" {
        description
          "Initial version. YANG modeling of 5G nrf";
        yexte:version 1;
        yexte:release 0;
        yexte:correction 0;
    }

    container nrf {
        presence
          "";
        description
          "NRF configuration.";

        container common {
            description
              "NRF common configuration.";
            choice role {
                container plmn-nrf {
                    presence
                      "";
                    description
                      "NRF is configured as PLMN NRF.";
                    leaf mode {
                        type enumeration{
                            enum forward {
                                value 0;
                                description
                                  "Forwarding mode.";
                            }
                            enum redirect {
                                value 1;
                                description
                                  "Redirecting mode.";
                            }
                        }
                        default forward;
                        description
                          "In NRF layered deployment, the PLMN NRF mode to handle discovery or subscription.";
                    }
                }
                container region-nrf {
                    description
                      "NRF is configured as region NRF.";
                    container next-hop {
                        description
                          "The same/upper layer NRFs, towards which region NRF registers itself and 
                           forwards discovery request in case no match result within region itself.";

                        leaf mode {
                            type nrfce:load-balance-mode;
                            default active-standby;
                            description
                              "Traffic load balance mode among different NRFs in the same pool.";
                        }
                        list pool {
                            description
                              "NRFs in each pool belong to a geographical redundancy system.";
                            key id;
                            leaf id {
                                type string;
                                mandatory true;
                                description
                                  "Unique ID represents the pool of NRFs.";
                            }
                            leaf layer {
                                type enumeration{
                                    enum same-layer {
                                        value 0;
                                        description
                                          "Same layer NRF pool.";
                                    }
                                    enum upper-layer {
                                        value 1;
                                        description
                                          "Upper layer NRF pool.";
                                    }
                                }
                                default same-layer;
                                description
                                  "NRF pool is in the same layer or upper layer.";
                            }
                            list profile {
                                description
                                  "NRF profile of next hop.";
                                key "id";
                                uses nrfce:nrf-server-profile;
                                must 'fqdn or ipv4-address or ipv6-address' {
                                    error-message
                                      "At least one of the addressing parameters (fqdn, ipv4address, ipv6adress) must be included in the NRF Profile.";
                                }
                            }
                        }
                    }
                }
            }
            must 'plmn-nrf or region-nrf' {
                error-message
                  "At least one container (region-nrf or plmn-nrf) should be defined.";
            }
            // add CM for NRF geographical redundancy function
            container geo-red {
                description
                  "Additional options to control NRF service availability status when Geographical Redundancy function encounters external faults. The Geographical Redundancy function itself has to be setup manually according to user guide.";
                leaf keep-management-service {
                    type boolean;
                    default true;
                    description
                      "NRF NFManagement Service keeps handling service requests even if Geographical Redundancy function detects that this NRF leaves the redundancy configuration. This applies also for provisioning service.";
                }
                leaf keep-discovery-service {
                    type boolean;
                    default true;
                    description
                      "NRF NFDiscovery Service keeps handling service requests even if Geographical Redundancy function detects that this NRF leaves the redundancy configuration.";
                }

                container witness-nf {
                    description
                      "Witness NF used to assist NRF Geographical Redundancy function to select leading NRF.";

                    leaf identity-type {
                        type enumeration {
                            enum nf-fqdn {
                                value 0;
                                description
                                  "Use fqdn of the root NF Profile as key to specify the witness NF instance.";
                            }
                            enum nf-instance-id {
                                value 1;
                                description
                                  "Use nfInstanceId of the root NF Profile as key to specify the witness NF instance.";
                            }
                        }
                        description
                          "To specify the identity type of the witness NF";
                    }

                    leaf identity-value {
                        type string;
                        description
                          "To specify the fqdn or nfInstanceId of the witness NF";
                    }
                }
            }
        }

        container nf-profile {
            description
              "NRF own NFProfile info.";
            uses udmp5gce:nf-profile;

            must 'fqdn or ipv4-address or ipv6-address' {
                error-message
                  "At least one of the addressing parameters (fqdn, ipv4address, ipv6adress) must be included in the NRF Profile.";
            }

            list service {
                description
                  "NRF service info.";
                key "instance-id";
                min-elements 2;
                uses udmp5gce:nf-service;
                must 'name = "nnrf-nfm" or name = "nnrf-disc"' {
                    error-message
                      "Service name for NRF is not correct.";
                }
            }
        }
        container management-service {
            description
              "NRF mangement service configuration.";
            uses management-service;
        }

        container discovery-service {
            description
              "NRF discovery service configuration.";
            uses discovery-service;
        }

        container provisioning-service {
            description
              "NRF provisioning service configuration.";
            uses provisioning-service;
        }

        container policy {
            description
              "NRF policy configuration.";
            uses nrf-policy;
        }
        tailf:callpoint cpa;
    }
}
