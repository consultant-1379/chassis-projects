// Generated by EYangPreprocessorUtil (1.12.0-SNAPSHOT 2019-10-09 17:32:48 CEST) on Oct 11, 2019 7:24:24 AM
module ericsson-5gcudmpol-common {
    yang-version 1.1;
    namespace urn:rdns:com:ericsson:oammodel:ericsson-5gcudmpol-common;
    prefix udmp5gce;
    import tailf-common {
        prefix tailf;
    }
    import ericsson-yang-extensions {
        prefix yexte;
    }

    import ietf-yang-types {
        prefix yang;
    }

    import ietf-inet-types {
        prefix inet;
    }

    organization
      "Ericsson AB";
    contact
      "Carlos Moya Serrano - ECARMOY - carlos.moya.serrano@ericsson.com";
    description
      "The module contains common definitions  
       for UDM and Policy 5GC NFs.       
       Copyright (c) 2019 Ericsson AB. All rights reserved.";

    revision 2019-09-25 {
        description
          "Errors in some special characters on description fields corrected.";
        yexte:version 1;
        yexte:release 0;
        yexte:correction 1;
    }

    revision 2019-06-20 {
        description
          "NF Service version definition updated. config false added and min-elements 1 statement removed.
		  typedef nf-scheme added.
		  NF Service scheme type changed to nf-scheme.
		  NF Profile status renamed to requested-status, default value set to SUSPENDED and mandatory statement removed.
		  remote-nf-profile and remote-nf-service groupings added.";
        yexte:version 1;
        yexte:release 0;
        yexte:correction 0;
    }

    revision 2019-06-19 {
        description
          "Characters ^ and $ removed from all pattern definitions.";
        yexte:version 0;
        yexte:release 1;
        yexte:correction 5;
    }

    revision 2019-04-01 {
        description
          "mandatory statement removed for type leaf at nf-profile grouping.
		   config false statement added to api-prefix leaf definition at nf-service grouping.";
        yexte:version 0;
        yexte:release 1;
        yexte:correction 4;
    }

    revision 2019-03-28 {
        description
          "Align with UDM&P solution study.";
        yexte:version 0;
        yexte:release 1;
        yexte:correction 3;
    }

    revision 2019-03-21 {
        description
          "Align with UDM&P solution study.";
        yexte:version 0;
        yexte:release 1;
        yexte:correction 2;
    }

    revision 2019-01-16 {
        description
          "Align with 29.510 15.2.0 version,
           Move NRFAgent configuration to separate module.";
        reference
          "RFC 7950: The YANG 1.1 Data Modeling Language";
        yexte:version 0;
        yexte:release 1;
        yexte:correction 1;
    }

    revision 2018-11-02 {
        description
          "Initial revision.";
        reference
          "RFC 7950: The YANG 1.1 Data Modeling Language";
        yexte:version 0;
        yexte:release 1;
        yexte:correction 0;
    }

    typedef nf-scheme {
        type enumeration {
            enum "http" {
                value 1;
                description
                  "NF service endpoint using HTTP scheme";
            }
            enum "https" {
                value 2;
                description
				"NF service endpoint using HTTPs scheme";
            }
        }
    }

    typedef nf-type {
        type enumeration {
            enum "nrf" {
                value 1;
                description  "NRF";
            }
            enum "udm" {
                value 2;
                description  "UDM";
            }
            enum "amf" {
                value 3;
                description  "AMF";
            }
            enum "smf" {
                value 4;
                description  "SMF";
            }
            enum "ausf" {
                value 5;
                description  "AUSF";
            }
            enum "nef" {
                value 6;
                description  "NEF";
            }
            enum "pcf" {
                value 7;
                description  "PCF";
            }
            enum "smsf" {
                value 8;
                description  "SMSF";
            }
            enum "nssf" {
                value 9;
                description  "NSSF";
            }
            enum "udr" {
                value 10;
                description "UDR";
            }
            enum "lmf" {
                value 11;
                description "LMF";
            }
            enum "gmlc" {
                value 12;
                description  "GMLC";
            }
            enum "5g-eir" {
                value 13;
                description "5G_EIR";
            }
            enum "sepp" {
                value 14;
                description "SEPP";
            }
            enum "upf" {
                value 15;
                description "UPF";
            }
            enum "n3iwf" {
                value 16;
                description "N3IWF";
            }
            enum "af" {
                value 17;
                description "AF";
            }
            enum "udsf" {
                value 18;
                description "UDSF";
            }
            enum "bsf" {
                value 19;
                description "BSF";
            }
            enum "chf" {
                value 20;
                description "CHF";
            }
            enum "nwdaf" {
                value 21;
                description "NWDAF";
            }
        }
        description
          "Type of Network Function.";
    }

    typedef nf-status {
        type enumeration {
            enum "registered" {
                value 1;
                description
                  "The NF Service Instance is registered in NRF and can be discovered by other NFs";
            }
            enum "suspended" {
                value 2;
                description
                  "The NF Service Instance is registered in NRF but it is not operative and cannot be discovered by other NFs. This status may result from a NF Service failure and may trigger restoration procedures";
            }
            enum "deregistered" {
                value 3;
                description
                  "The NF Service Instance is de-registered in NRF.";
            }
        }
        description
          "Status of the Network Function.";
    }

    typedef nf-service-status {
        type enumeration {
            enum "registered" {
                value 1;
                description
                  "REGISTERED";
            }
            enum "suspended" {
                value 2;
                description
                  "SUSPENDED";
            }
        }
        description
          "Status of the NF Service Instance.";
    }

    typedef transport-protocol {
        type enumeration {
            enum "tcp" {
                value 1;
                description
                  "TCP";
            }
        }
        description
          "Transport protocol.";
    }

    grouping plmn-id {
        leaf mcc {
            mandatory true;
            type string {
                pattern '[0-9]{3}';
            }
            tailf:callpoint cpa;
        }
        leaf mnc {
            mandatory true;
            type string {
                pattern '[0-9]{2,3}';
            }
            tailf:callpoint cpa;
        }
    }

    grouping s-nssai {
        leaf sst {
            mandatory true;
            type uint8 {
                range "0 .. 255";
            }
            tailf:callpoint cpa;
        }
        leaf sd {
            type string {
                pattern '[A-Fa-f0-9]{6}';
            }
            tailf:callpoint cpa;
        }
    }

    grouping ip-endpoint {
        choice address {
            leaf ipv4-address {
                type inet:ipv4-address;
            }
            leaf ipv6-address {
                type inet:ipv6-address;
            }
        }
        leaf transport {
            type transport-protocol;
            tailf:callpoint cpa;
        }
        leaf port {
            type inet:port-number {
            }
            tailf:callpoint cpa;
        }
    }

    typedef supported-features {
        type string {
            pattern '[A-Fa-f0-9]*';
        }
    }

    grouping supi-range {
        choice supi {
            case start-end-format {
                leaf supi-start {
                    type string {
                        pattern '[0-9]+';
                    }
                }
                leaf supi-end {
                    type string {
                        pattern '[0-9]+';
                    }
                }
            }
            case pattern-format {
                leaf supi-pattern {
                    type string {
                    }
                }
            }
        }
    }

    grouping identity-range {
        choice identity-range {
            case start-end-format {
                leaf identity-start {
                    type string {
                        pattern '[0-9]+';
                    }
                }
                leaf identity-end {
                    type string {
                        pattern '[0-9]+';
                    }
                }
            }
            case pattern-format {
                leaf identity-pattern {
                    type string {
                    }
                }
            }
        }
    }

    typedef dataset-id {
        type enumeration {
            enum "subscription" {
                value 1;
                description
                  "SUBSCRIPTION";
            }
            enum "policy" {
                value 2;
                description
                  "POLICY";
            }
            enum "exposure" {
                value 3;
                description
                  "EXPOSURE";
            }
            enum "application" {
                value 4;
                description
                  "APPLICATION";
            }
        }
    }

    grouping guami {
        container plmn-id {
            uses plmn-id;
            tailf:callpoint cpa;
        }
        leaf amf-id {
            type string {
                pattern
                  '[A-Fa-f0-9]{6}';
            }
            tailf:callpoint cpa;
        }
    }

    grouping tai {
        container plmn-id {
            uses plmn-id;
            tailf:callpoint cpa;
        }
        leaf tac {
            type string {
                pattern '([A-Fa-f0-9]{4})|([A-Fa-f0-9]{6})';
            }
            tailf:callpoint cpa;
        }
    }

    grouping ipv4address-range {
        leaf ipv4addr-start {
            type inet:ipv4-address;
            tailf:callpoint cpa;
        }
        leaf ipv4addr-end {
            type inet:ipv4-address;
            tailf:callpoint cpa;
        }
    }

    grouping nf-service-version {
        leaf api-version-in-uri {
            type  string {
            }
            tailf:callpoint cpa;
        }
        leaf api-full-version {
            type string {
            }
            tailf:callpoint cpa;
        }
        leaf expiry {
            type yang:date-and-time;
            tailf:callpoint cpa;
        }
    }

    typedef notification-type {
        type enumeration {
            enum "n1-messages" {
                value 1;
                description
                  "N1_MESSAGES";
            }
            enum "n2-information" {
                value 2;
                description
                  "N2_INFORMATION";
            }
            enum "location-notification" {
                value 3;
                description
                  "LOCATION_NOTIFICATION";
            }
            enum "data-removal-notification" {
                value 4;
                description
                  "DATA_REMOVAL_NOTIFICATION";
            }
            enum "data-change-notification" {
                value 5;
                description
                  "DATA_CHANGE_NOTIFICATION";
            }
        }
    }

    typedef n1-message-class {
        type enumeration {
            enum "5gmm" {
                value 1;
                description
                  "5GMM";
            }
            enum "sm" {
                value 2;
                description
                  "SM";
            }
            enum "lpp" {
                value 3;
                description
                  "LPP";
            }
            enum "sms" {
                value 4;
                description
                  "SMS";
            }
            enum "updp" {
                value 5;
                description
                  "UPDP";
            }
        }
    }

    typedef n2-information-class {
        type enumeration {
            enum "sm" {
                value 1;
                description
                  "SM";
            }
            enum "nrppa" {
                value 2;
                description
                  "NRPPa";
            }
            enum "pws" {
                value 3;
                description
                  "PWS";
            }
            enum "pws-bcal" {
                value 4;
                description
                  "PWS-BCAL";
            }
            enum "pws-rf" {
                value 5;
                description
                  "PWS-RF";
            }
            enum "ran" {
                value 6;
                description
                  "RAN";
            }
        }
    }
    grouping default-notification-subscription {
        leaf notification-type {
            mandatory true;
            type notification-type {
            }
            tailf:callpoint cpa;
        }
        leaf callback-uri {
            type inet:uri;
            mandatory true;
            tailf:callpoint cpa;
        }
        leaf n1-message-class {
            type n1-message-class;
            tailf:callpoint cpa;
        }
        leaf n2-information-class {
            type n2-information-class;
            tailf:callpoint cpa;
        }
    }

    grouping nf-profile {
        leaf instance-id {
            mandatory true;
            type yang:uuid;
            description 
				"Unique identity of the NF Instance.";
            tailf:callpoint cpa;
        }
        leaf type {
            config false;
            type nf-type {
            }
            tailf:callpoint cpa;
        }
        leaf requested-status {
            type nf-status;
            default "suspended";
            description 
				"Administrative status requested to be set in registration process at NRF. When set to \"registered\" or \"suspended\", that shall be the value of the NFStatus parameter in the registration/update request towards NRF. When set to \"deregistered\", the Network Function's registration profile data shall be deleted from NRF.";
            tailf:callpoint cpa;
        }
        leaf requested-heartbeat-timer {
            type uint16;
            description
				"Time in seconds expected between 2 consecutive heart-beat messages from an NF Instance to the NRF,
				to be included in the registration request.";
            tailf:callpoint cpa;
        }
        list plmn-id {
            key "mcc mnc";
            uses plmn-id;
            description
				"PLMNs of the Network Function.";
            tailf:callpoint cpa;
        }
        list snssai {
            key "id";
            leaf id {
                type uint32;
            }
            uses s-nssai;
            description
				"S-NSSAIs of the Network Function.";
            tailf:callpoint cpa;
        }
        leaf-list nsi {
            type string;
            description
				"NSI identities of the Network Function.";
            tailf:callpoint cpa;
        }
        leaf fqdn {
            type string;
            description
				"FQDN of the Network Function.";
            tailf:callpoint cpa;
        }
        leaf inter-plmn-fqdn {
            type string;
            description
				"If the NF needs to be discoverable by other NFs in a different PLMN,
				then an FQDN that is used for inter PLMN routing as specified in 3GPP TS 23.003 needs to be registered with the NRF.";
            tailf:callpoint cpa;
        }
        leaf-list ipv4-address {
            type inet:ipv4-address;
            description
				"IPv4 addresses of the Network Function.";
            tailf:callpoint cpa;
        }
        leaf-list ipv6-address {
            type inet:ipv6-address;
            description
				"IPv6 addresses of the Network Function.";
            tailf:callpoint cpa;
        }
        list allowed-plmn {
            key "mcc mnc";
            uses plmn-id;
            description
				"PLMNs allowed to access the NF instance.";
            tailf:callpoint cpa;
        }
        leaf-list allowed-nf-type {
            type nf-type;
            description
				"Type of the NFs allowed to access the NF instance.";
            tailf:callpoint cpa;
        }
        leaf-list allowed-nf-domain {
            type string;
            description
			   "Pattern (regular expression according to the ECMA-262 dialect) representing the NF domain names allowed to access the NF instance.";
            tailf:callpoint cpa;
        }
        list allowed-nssai {
            key "id";
            leaf id {
                type uint32;
            }
            uses s-nssai;
            description
                "S-NSSAI of the allowed slices to access the NF instance.";
            tailf:callpoint cpa;
        }
        leaf priority {
            type uint16 {
                range "0 .. 65535";
            }
            description
				"Priority (relative to other NFs of the same type) in the range of 0-65535, to be used for NF selection;
				lower values indicate a higher priority. If priority is also present in the nfServiceList parameters, those will have precedence over this value.";
            tailf:callpoint cpa;
        }
        leaf capacity {
            type uint16 {
                range "0 .. 65535";
            }
            description
				"Static capacity information in the range of 0-65535, expressed as a weight relative to other NF instances of the same type;
				if capacity is also present in the nfServiceList parameters, those will have precedence over this value.";
            tailf:callpoint cpa;
        }
        leaf locality {
            type string;
            description
				"Operator defined information about the location of the NF instance.";
            tailf:callpoint cpa;
        }
        leaf recovery-time {
            type yang:date-and-time;
            description
				"Timestamp when the NF was (re)started.";
            tailf:callpoint cpa;
        }
        leaf service-persistence {
            config false;
            type boolean;
            description
				"If present, and set to true, it indicates that the different service instances of a same NF Service in this NF instance,
				supporting a same API version, are capable to persist their resource state in shared storage and therefore these resources are available
				after a new NF service instance supporting the same API version is selected by a NF Service Consumer.";
            tailf:callpoint cpa;
        }
    }

    grouping nf-service {
        leaf instance-id {
            mandatory true;
            type string;
            description
					"Unique ID of the service instance within the NF Instance.";
            tailf:callpoint cpa;
        }
        leaf name {
            mandatory true;
            type string;
            description
					"Name of the service instance.";
            tailf:callpoint cpa;
        }
        list version {
            key "api-version-in-uri";
            config false;
            uses nf-service-version;
            description
					"The API versions supported by the NF Service and if available, the corresponding retirement date of the NF Service.";
            tailf:callpoint cpa;
        }
        leaf scheme {
            mandatory true;
            type nf-scheme;
            description
					"URI scheme.";
            tailf:callpoint cpa;
        }
        leaf status {
            mandatory true;
            type nf-service-status;
            tailf:callpoint cpa;
        }
        leaf fqdn {
            type string;
            description
					"FQDN of the NF Service Instance.";
            tailf:callpoint cpa;
        }
        leaf inter-plmn-fqdn {
            type string;
            description
					"If the NF service needs to be discoverable by other NFs in a different PLMN,
					then an FQDN that is used for inter PLMN routing as specified in 3GPP TS 23.003 may be registered with the NRF.";
            tailf:callpoint cpa;
        }
        list ip-endpoint {
            key "id";
            leaf id {
                type uint32;
            }
            uses ip-endpoint;
            description
					"IP addresses and port information of the Network Function (including IPv4 and/or IPv6 address)
					where the service is listening for incoming service requests.";
            tailf:callpoint cpa;
        }
        leaf api-prefix {
            config false;
            type string;
            description
					"Optional path segment used to construct the {apiRoot} variable of the different API URIs, as described in 3GPP TS 29.501";
            tailf:callpoint cpa;
        }
        list default-notification-subscription {
            key "notification-type callback-uri";
            uses default-notification-subscription;
            description
					"Notification endpoints for different notification types.";
            tailf:callpoint cpa;
        }
        list allowed-plmn {
            key "mcc mnc";
            uses plmn-id;
            description
					"PLMNs allowed to access the service instance. The absence of this attribute indicates that any PLMN is allowed to access the service instance.
					When included, the allowedPlmns attribute needs not include the PLMN IDs registered in the plmnList attribute of the NF Profile,
					i.e. the PLMN IDs registered in the NF Profile shall be considered to be allowed to access the service instance.";
            tailf:callpoint cpa;
        }
        leaf-list allowed-nf-type {
            type nf-type;
            description
					"Type of the NFs allowed to access the service instance.
					The absence of this attribute indicates that any NF type is allowed to access the service instance.";
            tailf:callpoint cpa;
        }
        leaf-list allowed-nf-domain {
            type string;
            description
					"Pattern (regular expression according to the ECMA-262 dialect) representing the NF domain names allowed to access the service instance.
					The absence of this attribute indicates that any NF domain is allowed to access the service instance.";
            tailf:callpoint cpa;
        }
        list allowed-nssai {
            key "id";
            leaf id {
                type uint32;
            }
            uses s-nssai;
            description
					"S-NSSAI of the allowed slices to access the service instance.
					The absence of this attribute indicates that any slice is allowed to access the service instance.";
            tailf:callpoint cpa;
        }
        leaf priority {
            type uint16 {
                range "0 .. 65535";
            }
            description
					"Priority (relative to other services of the same type) in the range of 0-65535
					to be used for NF Service selection; lower values indicate a higher priority.";
            tailf:callpoint cpa;
        }
        leaf capacity {
            type uint16 {
                range "0 .. 65535";
            }
            description
					"Static capacity information in the range of 0-65535, expressed as a weight relative to other services of the same type.";
            tailf:callpoint cpa;
        }
        leaf recovery-time {
            type yang:date-and-time;
            description
					"Timestamp when the NF service was (re)started.";
            tailf:callpoint cpa;
        }
        leaf supported-features {
            config false;
            type supported-features;
            description
					"Supported Features of the NF Service instance.";
            tailf:callpoint cpa;
        }
    }

    grouping ausf-info {
        leaf group-id {
            type string;
            tailf:callpoint cpa;
        }
        list supi-range {
            key "id";
            leaf id {
                type uint32;
            }
            uses supi-range;
            tailf:callpoint cpa;
        }
        leaf-list routing-indicator {
            type string;
            tailf:callpoint cpa;
        }
    }

    grouping udr-info {
        leaf group-id {
            type string;
            tailf:callpoint cpa;
        }
        list supi-range {
            key "id";
            leaf id {
                type uint32;
            }
            uses supi-range;
            tailf:callpoint cpa;
        }
        list gpsi-range {
            key "id";
            leaf id {
                type uint32;
            }
            uses identity-range;
            tailf:callpoint cpa;
        }
        list external-group-identifiers-range {
            key "id";
            leaf id {
                type uint32;
            }
            uses identity-range;
            tailf:callpoint cpa;
        }
        leaf-list supported-data-set {
            type dataset-id;
            tailf:callpoint cpa;
        }
    }
    grouping udm-info {
        leaf group-id {
            type string;
            tailf:callpoint cpa;
        }
        list supi-range {
            key "id";
            leaf id {
                type uint32;
            }
            uses supi-range;
            tailf:callpoint cpa;
        }
        list gpsi-range {
            key "id";
            leaf id {
                type uint32;
            }
            uses identity-range;
            tailf:callpoint cpa;
        }
        list external-group-identifiers-range {
            key "id";
            leaf id {
                type uint32;
            }
            uses identity-range;
            tailf:callpoint cpa;
        }
        leaf-list routing-indicator {
            type string;
            tailf:callpoint cpa;
        }
    }

    grouping pcf-info {
        leaf-list dnn {
            type string;
            tailf:callpoint cpa;
        }
        list supi-range {
            key "id";
            leaf id {
                type uint32;
            }
            uses supi-range;
            tailf:callpoint cpa;
        }
        leaf rx-diam-host {
            type string {
                pattern '([A-Za-z0-9]+(-[A-Za-z0-9]+).)+[a-z]{2,}';
            }
            tailf:callpoint cpa;
        }
        leaf rx-diam-realm {
            type string {
                pattern '([A-Za-z0-9]+(-[A-Za-z0-9]+).)+[a-z]{2,}';
            }
            tailf:callpoint cpa;
        }
    }

    grouping remote-nf-profile {
        leaf type {
            mandatory true;
            type udmp5gce:nf-type {
            }
            tailf:callpoint cpa;
        }
        leaf fqdn {
            type string;
            description
              "FQDN of the Network Function.";
            tailf:callpoint cpa;
        }
        leaf-list ipv4-address {
            type inet:ipv4-address;
            description
              "IPv4 addresses of the Network Function.";
            tailf:callpoint cpa;
        }
        leaf-list ipv6-address {
            type inet:ipv6-address;
            description
              "IPv6 addresses of the Network Function.";
            tailf:callpoint cpa;
        }
    }

    grouping remote-nf-service {
        leaf name {
            mandatory true;
            type string;
            description
              "Name of the service instance.";
            tailf:callpoint cpa;
        }
        leaf fqdn {
            type string;
            description
              "FQDN of the NF Service Instance.";
            tailf:callpoint cpa;
        }
        list ip-endpoint {
            key "id";
            leaf id {
                type uint32;
            }
            uses udmp5gce:ip-endpoint;
            description
              "IP addresses and port information of the Network Function (including IPv4 and/or IPv6 address)
               where the service is listening for incoming service requests.";
            tailf:callpoint cpa;
        }
        list default-notification-subscription {
            key "notification-type callback-uri";
            uses udmp5gce:default-notification-subscription;
            description
              "Notification endpoints for different notification types.";
            tailf:callpoint cpa;
        }
    }
}
