// Generated by EYangPreprocessorUtil (1.12.0-SNAPSHOT 2019-10-09 17:32:48 CEST) on Oct 11, 2019 7:24:25 AM
submodule nrf-submodule-provisioning {
    yang-version "1.1";

    // module identification
    belongs-to ericsson-nrf {
        prefix "nrfe";
    }

    // linkage statements
    import tailf-common {
        prefix tailf;
    }
    import ericsson-yang-extensions {
        prefix yexte;
    }

    import ericsson-5gcudmpol-common {
        prefix udmp5gce;
    }

    organization
      "Ericsson AB";
    contact
      "Ericsson first line support via email";
    description
      "nrf submodule discovery.
       Copyright (c) 2018 Ericsson AB. All rights reserved.";

    revision "2019-09-04" {
        description
          "1, refine cm modeling;
           2, update ericsson-5gcudmpol-common to v1.0.1";
        yexte:version 0;
        yexte:release 1;
        yexte:correction 3;
    }

    revision "2019-04-24" {
        description
          "Change to use ip-endpoint";
        yexte:version 0;
        yexte:release 1;
        yexte:correction 2;
    }

    revision "2018-11-08" {
        description
          "Change address id type";
        yexte:version 0;
        yexte:release 1;
        yexte:correction 1;
    }

    revision "2018-09-17" {
        description
          "Initial version. YANG modeling of 5G nrf provisioning";
        yexte:version 0;
        yexte:release 1;
        yexte:correction 0;
    }

    // module definitions
    grouping provisioning-service {

        list prov-address {
            description
              "NRF provisioning service address configuration.";
            key "id";
            leaf id {
                type uint32;
                mandatory true;
                description
                  "Unique id.";
            }

            leaf scheme {
                type udmp5gce:nf-scheme;
                mandatory true;
                description
                  "Protocol scheme eg http, https.";
            }

            leaf fqdn {
                type string;
                description
                  "FQDN of the NF where the service is hosted.";
            }
            uses udmp5gce:ip-endpoint;
            must 'fqdn or ipv4-address or ipv6-address' {
                error-message
                  "At least one of the addressing parameters (fqdn, ipv4address, ipv6adress) must be included in provisioning service.";
            }
            tailf:callpoint cpa;
        }
    }
}
