// Generated by EYangPreprocessorUtil (1.12.0-SNAPSHOT 2019-10-09 17:32:48 CEST) on Oct 11, 2019 7:24:24 AM
module ericsson-nrf-common {
    yang-version 1.1;
    namespace urn:rdns:com:ericsson:oammodel:ericsson-nrf-common;
    prefix nrfce;

    import tailf-common {
        prefix tailf;
    }
    import ietf-inet-types {
        prefix inet;
    }
    import ericsson-yang-extensions {
        prefix yexte;
    }
    import ericsson-5gcudmpol-common {
        prefix udmp5gce;
    }
    organization
      "Ericsson AB";
    contact
      "Ericsson first line support via email";
    description
      "The module defines the data model for NRF.          
       Copyright (c) 2018 Ericsson AB. All rights reserved.";

    revision "2019-09-04" {
        description
          "1, refine cm modeling;
           2, update ericsson-5gcudmpol-common to v1.0.1";
        yexte:version 0;
        yexte:release 1;
        yexte:correction 6;
    }

    revision "2019-04-08" {
        description
          "Update nrf-server-profile";
        yexte:version 0;
        yexte:release 1;
        yexte:correction 5;
    }

    revision "2019-03-28" {
        description
          "align with ericsson-5gcudmpol-common 0.1.2";
        yexte:version 0;
        yexte:release 1;
        yexte:correction 4;
    }

    revision "2019-01-14" {
        description
          "Update to align 29.510 version 15.2.0";
        yexte:version 0;
        yexte:release 1;
        yexte:correction 3;
    }

    revision "2018-11-08" {
        description
          "Move common type to ericsson-5gcudmpol-common module and align version 15.1.0";
        yexte:version 0;
        yexte:release 1;
        yexte:correction 2;
    }

    revision "2018-09-03" {
        description
          "Update name convention; add nrf_server_profile";
        yexte:version 0;
        yexte:release 1;
        yexte:correction 1;
    }

    revision "2018-07-31" {
        description
          "Initial version. YANG modeling of common types";
        yexte:version 0;
        yexte:release 1;
        yexte:correction 0;
    }

    grouping nrf-server-profile {
        leaf id {
            type string;
            mandatory true;
            description
              "Unique ID represents the NRF.";
            tailf:callpoint cpa;
        }

        leaf fqdn {
            type string;
            description
              "FQDN of the NRF.";
            tailf:callpoint cpa;
        }

        leaf-list ipv4-address {
            type inet:ipv4-address;
            description
              "IPv4 address(es) of the the NRF.";
            tailf:callpoint cpa;
        }

        leaf-list ipv6-address {
            type inet:ipv6-address;
            description
              "IPv6 address(es) of the the NRF.";
            tailf:callpoint cpa;
        }
        leaf priority {
            type uint16  {
                range "0 .. 65535";
            }
            description
              "Priority of this NRF compared to the set of NRF in redundancy mode;lower values indicate a higher priority
               If priority is also present in the service parameters, those will have precedence over this value.";
            tailf:callpoint cpa;
        }

        leaf capacity {
            type uint16  {
                range "0 .. 65535";
            }
            description
              "Static capacity information in the range of 0-65535, expressed as a weight relative to other NRF,
               If priority is also present in the service parameters, those will have precedence over this value.";
            tailf:callpoint cpa;
        }

        leaf locality {
            type string;
            description
              "Location of the NF instance.";
            tailf:callpoint cpa;
        }

        list service {
            key id;
            leaf id {
                type uint32;
                description
                  "Unique ID represents the NRF service.";
                mandatory true;
            }

            leaf name {
                type nrf-service-name;
                mandatory true;
                description
                  "Name of the NRF service.";
            }
            list version {
                key "api-version-in-uri";
                uses udmp5gce:nf-service-version;
                min-elements 1;
                description
                  "Versions of the service instance to be used in the URI for accessing the API.";
            }

            leaf scheme {
                type udmp5gce:nf-scheme;
                mandatory true;
                description
                  "Protocol scheme.";
            }
            leaf fqdn {
                type string;
                description
                  "FQDN of the service instance.";
            }
            list ip-endpoint {
                key "id";
                leaf id {
                    type uint32;
                }
                uses udmp5gce:ip-endpoint;
                description
                  "IP address(es) and port information where the service is listening for incoming service requests.";
            }
            leaf priority {
                type uint16  {
                    range "0 .. 65535";
                }
                description
                  "Priority to be used for NF Service selection.";
            }

            leaf capacity {
                type uint16  {
                    range "0 .. 65535";
                }
                description
                  "Static capacity information in the range of 0-65535, expressed as a weight relative to other services of 
                   the same type.";
            }
            leaf api-prefix {
                type string;
                description
                  "Optional path segment(s) used to construct the {apiRoot} variable of the different API URIs.";
            }
            leaf supported-features {
                type udmp5gce:supported-features;
                description
                  "Supported Features of the NF Service instance.";
            }
            tailf:callpoint cpa;
        }
    }
    grouping overload-redirection-profile {
        leaf enabled {
            type boolean;
            default false;
            description
              "Overload redirection feature enabled true/false.";
            tailf:callpoint cpa;
        }
        leaf mode {
            when "(../enabled = 'true')";
            type enumeration
                {
                enum auto {
                    value 0;
                    description
                      "Overload redirection mode is auto.";
                }
                enum manual {
                    value 1;
                    description
                      "Overload redirection mode is manual.";
                }
            }
            default auto;
            description
              "Overload redirection feature mode auto/manual.";
            tailf:callpoint cpa;
        }
        leaf-list redirection-url {
            type string;
            description
              "Overload redirection url only valid when overload redirection mode equal to manual.";
            tailf:callpoint cpa;
        }
    }
    typedef load-balance-mode {
        type enumeration {
            enum active-standby {
                value 1;
                description
                  "Mode of activeStandby.";
            }
            enum load-balance {
                value 2;
                description
                  "Mode of loadBalance.";
            }
        }
    }
    typedef nrf-service-name {
        type enumeration {
            enum "nnrf-nfm" {
                value 1;
                description
                  "3GPP serivice name of NRF management service.";
            }
            enum "nnrf-disc" {
                value 2;
                description
                  "3GPP serivice name of NRF discovery service.";
            }
        }
    }
}
