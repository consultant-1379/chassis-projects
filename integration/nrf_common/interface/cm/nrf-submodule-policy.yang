// Generated by EYangPreprocessorUtil (1.12.0-SNAPSHOT 2019-10-09 17:32:48 CEST) on Oct 11, 2019 7:24:25 AM
submodule nrf-submodule-policy {
    yang-version "1.1";

    // module identification
    belongs-to ericsson-nrf {
        prefix "nrfe";
    }

    // linkage statements
    import tailf-common {
        prefix tailf;
    }
    import ericsson-yang-extensions {
        prefix yexte;
    }

    import ericsson-5gcudmpol-common {
        prefix udmp5gce;
    }

    organization
      "Ericsson AB";
    contact
      "Ericsson first line support via email";
    description
      "NRF DNS service submodel.
       Copyright (c) 2018 Ericsson AB. All rights reserved.";

    revision "2019-09-04" {
        description
          "1, refine cm modeling;
           2, update ericsson-5gcudmpol-common to v1.0.1";
        yexte:version 0;
        yexte:release 1;
        yexte:correction 3;
    }

    revision "2019-04-03" {
        description
          "align design rule";
        yexte:version 0;
        yexte:release 1;
        yexte:correction 2;
    }

    revision "2019-03-28" {
        description
          "align with ericsson-5gcudmpol-common 0.1.2";
        yexte:version 0;
        yexte:release 1;
        yexte:correction 1;
    }

    revision "2019-01-15" {
        description
          "Creation";
        yexte:version 0;
        yexte:release 1;
        yexte:correction 0;
    }

    // module definitions
    grouping nrf-policy {
        container management-service {
            description
              "NRF management servcie policy configuration.";
            container subscription {
                description
                  "The subscription policy.";
                list allowed-subscription-to-all-nfs {
                    description
                      "Policy for subscriptions to all NFs without subscrCond in SubscriptionData.
                         Set allowed-nf-type alone, or set it together with allowed-nf-domains to configure the subscription policy for the NFs which are allowed to subscribe to all NFs.
                         By default, NRF rejects subscriptions to all NFs.";
                    key "id";
                    leaf id {
                        type uint32;
                        description
                          "Unique id.";
                    }
                    leaf allowed-nf-type {
                        type udmp5gce:nf-type;
                        mandatory true;
                        description
                          "The type of NF which is allowed to subscribe to all NFs.";
                    }
                    leaf allowed-nf-domains {
                        type string;
                        description
                          "Pattern(regular expression) representing the NF domain names allowed to subscribe to all NFs.
                           If present, NRF allows those subscriptions whose reqNfFqdn matches the defined pattern to subscribe to all NFs.";
                    }
                }
            }
            tailf:callpoint cpa;
        }
        container sbi-message-priority-policy {
            description
              "Range definition of priority groups (high, medium, low), by default, high:(0..7) medium:(8..15) low:(16..31).";
            leaf priority-group-medium-start {
                type uint32{
                    range "0..31";
                }
                must ". > 0" {
                    error-message
                      "The value must be larger than 0.";
                }
                default 8;
                description
                  "Value of priority policy group medium start.";
            }
            leaf priority-group-low-start {
                type uint32{
                    range "0..31";
                }
                default 16;
                description
                  "Value of priority policy group low start.";
            }
            must "priority-group-low-start > priority-group-medium-start" {
                error-message
                  "priority-group-low-start must larger than priority-group-medium-start.";
            }
            leaf default-message-priority {
                type uint32{
                    range "0..31";
                }
                default 24;
                description
                  "Defualt message priority value.";
            }
            tailf:callpoint cpa;
        }
    }
}
