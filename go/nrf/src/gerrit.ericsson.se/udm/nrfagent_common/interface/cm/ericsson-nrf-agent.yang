// Generated by EYangPreprocessorUtil (1.11.0-SNAPSHOT 2019-03-06 23:30:14 CET) on Apr 15, 2019 10:14:09 AM
module ericsson-nrf-agent {
    yang-version 1.1;
    namespace urn:rdns:com:ericsson:oammodel:ericsson-nrf-agent;
    prefix nrfae;

    import tailf-common {
        prefix tailf;
    }
    import ericsson-yang-extensions {
        prefix yexte;
    }

    import ietf-inet-types {
        prefix inet;
    }

    import ericsson-5gcudmpol-common {
        prefix udmp5gce;
    }

    organization
      "Ericsson AB";
    contact
      "Ericsson first line support via email";
    description
      "The module defines the data model of common configuration 
       for UDM and Policy 5GC NFs.       
       Copyright (c) 2018 Ericsson AB. All rights reserved.";

    revision "2019-04-10" {
        description "align with design rule in UDM&P solution study";
        yexte:version 0;
        yexte:release 1;
        yexte:correction 2;
    }

    revision 2019-01-16 {
        description
          "Initial revision.";
        reference
          "RFC 7950: The YANG 1.1 Data Modeling Language";
        yexte:version 0;
        yexte:release 1;
        yexte:correction 1;
    }

    grouping nrf-server-profile {
        leaf id {
            type string {
            }
            mandatory true;
            description "Unique ID represents the NRF.";

            tailf:callpoint cpa;
        }

        leaf fqdn {
            type string {
            }
            description "FQDN of the NRF.";
            tailf:callpoint cpa;
        }

        leaf-list ipv4-address {
            type inet:ipv4-address {
            }
            tailf:callpoint cpa;
        }

        leaf-list ipv6-address {
            type inet:ipv6-address {
            }
            tailf:callpoint cpa;
        }

        leaf priority {
            type uint16  {
                range "0 .. 65535";
            }
            description "Priority of this NRF compared to the set of NRF in redundancy mode;lower values indicate a higher priority
			              If priority is also present in the service parameters, those will have precedence over this value.";
            tailf:callpoint cpa;
        }

        leaf capacity {
            type uint16  {
                range "0 .. 65535";
            }
            description "Static capacity information in the range of 0-65535, expressed as a weight relative to other NRF,
                         If priority is also present in the service parameters, those will have precedence over this value.";
            tailf:callpoint cpa;
        }

        leaf locality {
            type string {
            }
            tailf:callpoint cpa;
        }

        list service {
            key id;
            leaf id {
                type uint32 {
                }
                description "Unique ID represents the NRF service.";
            }

            leaf name {
                type string {
                }
                mandatory true;
            }
            list version {
                key "api-version-in-uri";
                uses udmp5gce:nf-service-version;
                min-elements 1;
                description "Versions of the service instance to be used in the URI for accessing the API";
            }

            leaf scheme {
                type string {
                }
                mandatory true;
                description "Protocol scheme.";
            }
            leaf fqdn {
                type string {
                }
                description "FQDN of the service instance.";
            }
            list ip-endpoint {
                key "id";
                leaf id {
                    type uint32;
                }
                uses udmp5gce:ip-endpoint;
                description "IP address(es) and port information where the service is listening for incoming service requests.";
            }
            leaf priority {
                type uint16  {
                    range "0 .. 65535";
                }
                description "Priority to be used for NF Service selection.";
            }

            leaf capacity {
                type uint16  {
                    range "0 .. 65535";
                }
                description "Static capacity information in the range of 0-65535, expressed as a weight relative to other services of 
                the same type.";
            }
            leaf api-prefix {
                type string {
                }
                description "Optional path segment(s) used to construct the {apiRoot} variable of the different API URIs.";
            }
            leaf supported-features {
                type udmp5gce:supported-features;
                description "Supported Features of the NF Service instance.";
            }
            tailf:callpoint cpa;
        }
    }

    typedef load-balance-mode {
        type enumeration {
            enum active-standby {
                value 1;
                description  "activeStandby";
            }
            enum load-balance {
                value 2;
                description  "loadBalance";
            }
        }
        description
          "Define the mode: loadBalance or activeStandby .";
    }

    container nrf-agent {
        presence "";
        description "Configuration for the NRFAgent";

        container nrf {
            description "Local configuration of NRFs that could be selected to connect.";
            leaf mode {
                type load-balance-mode;
                default active-standby;
            }
            list profile {
                key "id";
                uses nrf-server-profile;
                description "Each item of the list represents the connection point to a specific NRF which may include multiple services.";
            }
        }

        // Callback IP/port for notifiy agent
        container notification-address {
            uses udmp5gce:ip-endpoint;
            description "IP address and port used to construct nfStatusNotificationUri for incoming notifications from NRF.";
        }
        tailf:callpoint cpa;
    }
}
